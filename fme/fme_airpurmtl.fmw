FME workspace fme_airpurmtl.fmw

Parameters:
- SourceDataset_CSV2_6 = https://www150.statcan.gc.ca/n1/fr/pub/71-607-x/2022018/tf-ft-fra.csv?st=usMloofQ   # Source CSV (Comma Separated Value) File(s)
- SourceDataset_GEOJSON = https://donnees.montreal.ca/dataset/2e9e4d2f-173a-4c3d-a5e3-565d79baa27d/resource/35796624-15df-4503-a569-797665f8768e/download/espace_vert.json   # Source GeoJSON File or URL
- DestDataset_POSTGIS = BDGEO7630   # Connection
- DestDataset_LAS_3 = https:\\depot.ville.montreal.qc.ca\geomatique\lidar_aerien\2015\LAS2015_classifiees_300-307.zip   # Destination ASPRS LAS Folder
- DestDataset_LAS = https:\\depot.ville.montreal.qc.ca\geomatique\lidar_aerien\2015\LAS2015_classifiees_300-307.zip   # Destination ASPRS LAS Folder
- SourceDataset_GEOJSON_5 = https://donnees.montreal.ca/dataset/9797a946-9da8-41ec-8815-f6b276dec7e9/resource/6b313375-d9bc-4dc3-af8e-ceae3762ae6e/download/limites-administratives-agglomeration-nad83.geojson   # Source GeoJSON File or URL
- SourceDataset_CSV2_7 = https://donnees.montreal.ca/dataset/ae01f7f3-4d69-404a-9be1-74abfdc96571/resource/29db5545-89a4-4e4a-9e95-05aa6dc2fd80/download/liste-des-stations-rsqa.csv   # Source CSV (Comma Separated Value) File(s)
- SourceDataset_CSV2_9 = https://donnees.montreal.ca/dataset/3e9f7b96-3f25-4404-a5ad-22d9a31060e6/resource/a25fdea2-7e86-42ac-8301-ca77db3ff17e/download/rsqa-indice-qualite-air.csv   # Source CSV (Comma Separated Value) File(s)
- SourceDataset_CSV2_10 = https://donnees.montreal.ca/dataset/3e9f7b96-3f25-4404-a5ad-22d9a31060e6/resource/ccd5a4b7-cbca-4f5f-a746-ad8c576af374/download/rsqa-indice-qualite-air-station.csv   # Source CSV (Comma Separated Value) File(s)
- DestDataset_POSTGIS_13 = BDGEO7630   # Connection
- DestDataset_POSTGIS_9 = BDGEO7630   # Connection
- DestDataset_POSTGIS_11 = GEO7630H24   # Connection
- DestDataset_POSTGIS_8 = GEO7630H24   # Connection
- DestDataset_POSTGIS_10 = GEO7630H24   # Connection

Readers:
- CSV2_4: CSV2 from $(SourceDataset_CSV2_6)
- GEOJSON_1: GEOJSON from $(SourceDataset_GEOJSON)
- GEOJSON_2: GEOJSON from https://donnees.montreal.ca/dataset/ab112a84-0661-4360-9573-652eed16beeb/resource/a90678ac-7ea7-464c-b615-e8f5cb9f527b/download/rsqa_secteurs.geojson
- GEOJSON_3: GEOJSON from $(SourceDataset_GEOJSON_5)
- CSV2_1: CSV2 from $(SourceDataset_CSV2_7)
- CSV2_2: CSV2 from $(SourceDataset_CSV2_9)
- CSV2_3: CSV2 from $(SourceDataset_CSV2_10)

Writers:
- POSTGIS_1: POSTGIS to $(DestDataset_POSTGIS) in EPSG:3857
- LAS_1: LAS to $(DestDataset_LAS)
- LAS_2: LAS to $(DestDataset_LAS_3)
- POSTGIS_3: POSTGIS to $(DestDataset_POSTGIS_13) in EPSG:3857
- POSTGIS_2: POSTGIS to $(DestDataset_POSTGIS_9) in EPSG:3857
- POSTGIS_4: POSTGIS to $(DestDataset_POSTGIS_11) in EPSG:3857
- POSTGIS_5: POSTGIS to $(DestDataset_POSTGIS_8) in EPSG:3857
- POSTGIS_6: POSTGIS to $(DestDataset_POSTGIS_10)

Logger_8
    LOG_FEATURE = LOG_ONLY
    MAXCOORDS = 20
    MAXFEATS = 20
    MESSAGE = Feature is:
    SEVERITY = INFO
Note: REPROJECTION
Reprojector_5
    DEST = EPSG:3857
    INTERPOLATION_TYPE_NAME = Nearest Neighbor
    RASTER_CELL_SIZE = Preserve Cells
    RASTER_TOLERANCE = 0.0
    REPROJECTED -> espace_parc_mtl (writer POSTGIS_4)
Note: reporjection 3857
Reprojector
    DEST = EPSG:3857
    INTERPOLATION_TYPE_NAME = Nearest Neighbor
    RASTER_CELL_SIZE = Preserve Cells
    RASTER_TOLERANCE = 0.0
    REPROJECTED -> rsqa_secteurs_4326 (writer POSTGIS_5)
Note: connection base de donnees
rsqa_secteurs_4326 (writer POSTGIS_5)
    attributes: id int8, lettre text, nom text
Note: reporjection
Reprojector_2
    DEST = EPSG:3857
    INTERPOLATION_TYPE_NAME = Nearest Neighbor
    RASTER_CELL_SIZE = Preserve Cells
    RASTER_TOLERANCE = 0.0
Note: reprojection
Reprojector_8
    DEST = EPSG:3857
    INTERPOLATION_TYPE_NAME = Nearest Neighbor
    RASTER_CELL_SIZE = Preserve Cells
    RASTER_TOLERANCE = 0.0
    REPROJECTED -> AttributeManager_2
Note: supprime la colone polluant
AttributeManager
    ATTR_TABLE = REMOVE Polluant
    -> Station_1
Note: REPROJECTION 3857
Reprojector_11
    DEST = EPSG:3857
    INTERPOLATION_TYPE_NAME = Nearest Neighbor
    RASTER_CELL_SIZE = Preserve Cells
    RASTER_TOLERANCE = 0.0
    REPROJECTED -> SpatialFilter [Candidate]
Note: jointure spatiale
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> CoordinateSystemSetter
    <REJECTED> -> Logger_9
Note: projection en WG
CoordinateSystemSetter
    COORDSYS = LL-WGS84
    -> CoordinateExtractor_2
CoordinateExtractor_2
    LIST_NAME = _indices
    MODE = All Coordinates
Logger_9
    LOG_FEATURE = LOG_ONLY
    MAXCOORDS = 20
    MAXFEATS = 20
    MESSAGE = Feature is:
    SEVERITY = INFO
Logger_10
    LOG_FEATURE = LOG_ONLY
    MAXCOORDS = 20
    MAXFEATS = 20
    MESSAGE = Feature is:
    SEVERITY = INFO

Bookmark: Limites administratives
limites-administratives-agglomeration-nad83 (reader GEOJSON_3)
    attributes: CODEID int, NOM string, NOM_OFFICIEL string, CODEMAMH string, CODE_3C string, NUM int, ABREV string, TYPE string, COMMENT string, DATEMODIF string
    -> AttributeRemover_3
Note: Reprojector
Reprojector_10
    DEST = EPSG:3857
    INTERPOLATION_TYPE_NAME = Nearest Neighbor
    RASTER_CELL_SIZE = Preserve Cells
    RASTER_TOLERANCE = 0.0
    REPROJECTED -> PointOnAreaOverlayer_3 [AREA]
    REPROJECTED -> SpatialFilter [Filter]
    REPROJECTED -> limites-administratives-agglomeration-nad83 (writer POSTGIS_4)
Note: ajout dans la base de données
limites-administratives-agglomeration-nad83 (writer POSTGIS_4)
    attributes: codeid int8, nom text, nom_officiel text, codemamh text, code_3c text, num int8, abrev text, type text, comment text, datemodif text

Bookmark: netooyage
AttributeRemover_3
    REMOVE_ATTRS = CODE_3C,COMMENT,NOM_OFFICIEL,CODEMAMH
    -> Reprojector_10

Bookmark: Stations par arrondissement
PointOnAreaOverlayer_3
    ATTR_ACCUM_MODE = Merge Incoming
    ATTR_CONFLICT_RES = Use Original
    DEAGGREGATE_INPUT = Yes
    OV_ATTR = _overlaps
    POLYS_FIRST = NO
    <REJECTED> -> Logger_8

Bookmark: Traffic Routier brut
CSV (reader CSV2_4)
    attributes: WKT varchar(34), CSDUID real64, traffic_camera varchar(46), traffic_source varchar(9), camera_road varchar(82), x2022_02_02 real32, x2022_02_03 real32, x2022_02_04 real32, x2022_02_05 real32, x2022_02_06 real32, x2022_02_07 real32, x2022_02_08 real32, x2022_02_09 real32, x2022_02_10 real32, x2022_02_11 real32, x2022_02_12 real32, x2022_02_13 real32, x2022_02_14 real32, x2022_02_15 real32, x2022_02_16 real32, x2022_02_17 real32, x2022_02_18 real32, x2022_02_19 real32, x2022_02_20 real32, x2022_02_21 real32, x2022_02_22 real32, x2022_02_23 real32, x2022_02_24 real32, x2022_02_25 real32, x2022_02_26 real32,
      x2022_02_27 real32, x2022_02_28 real32, x2022_03_01 real32, x2022_03_02 real32, x2022_03_03 real32, x2022_03_04 real32, x2022_03_05 real32, x2022_03_06 real32, x2022_03_07 real32, x2022_03_08 real32, x2022_03_09 real32, x2022_03_10 real32, x2022_03_11 real32, x2022_03_12 real32, x2022_03_13 real32, x2022_03_14 real32, x2022_03_15 real32, x2022_03_16 real32, x2022_03_17 real32, x2022_03_18 real32, x2022_03_19 real32, x2022_03_20 real32, x2022_03_21 real32, x2022_03_22 real32, x2022_03_23 real32, x2022_03_24 real32, x2022_03_25 real32, x2022_03_26 real32, x2022_03_27 real32, x2022_03_28 real32,
      x2022_03_29 real32, x2022_03_30 real32, x2022_03_31 real32, x2022_04_01 real32, x2022_04_02 real32, x2022_04_03 real32, x2022_04_04 real32, x2022_04_05 real32, x2022_04_06 real32, x2022_04_07 real32, x2022_04_08 real32, x2022_04_09 real32, x2022_04_10 real32, x2022_04_11 real32, x2022_04_12 real32, x2022_04_13 real32, x2022_04_14 real32, x2022_04_15 real32, x2022_04_16 real32, x2022_04_17 real32, x2022_04_18 real32, x2022_04_19 real32, x2022_04_20 real32, x2022_04_21 real32, x2022_04_22 real32, x2022_04_23 real32, x2022_04_24 real32, x2022_04_25 real32, x2022_04_26 real32, x2022_04_27 real32,
      x2022_04_28 real32, x2022_04_29 real32, x2022_04_30 real32, x2022_05_01 real32, x2022_05_02 real32, x2022_05_03 real32, x2022_05_04 real32, x2022_05_05 real32, x2022_05_06 real32, x2022_05_07 real32, x2022_05_08 real32, x2022_05_09 real32, x2022_05_10 real32, x2022_05_11 real32, x2022_05_12 real32, x2022_05_13 real32, x2022_05_14 real32, x2022_05_15 real32, x2022_05_16 real32, x2022_05_17 real32, x2022_05_18 real32, x2022_05_19 real32, x2022_05_20 real32, x2022_05_21 real32, x2022_05_22 real32, x2022_05_23 real32, x2022_05_24 real32, x2022_05_25 real32, x2022_05_26 real32, x2022_05_27 real32,
      x2022_05_28 real32, x2022_05_29 real32, x2022_05_30 real32, x2022_05_31 real32, x2022_06_01 real32, x2022_06_02 real32, x2022_06_03 real32, x2022_06_04 real32, x2022_06_05 real32, x2022_06_06 real32, x2022_06_07 real32, x2022_06_08 real32, x2022_06_09 real32, x2022_06_10 real32, x2022_06_11 real32, x2022_06_12 real32, x2022_06_13 real32, x2022_06_14 real32, x2022_06_15 real32, x2022_06_16 real32, x2022_06_17 real32, x2022_06_18 real32, x2022_06_19 real32, x2022_06_20 real32, x2022_06_21 real32, x2022_06_22 real32, x2022_06_23 real32, x2022_06_24 real32, x2022_06_25 real32, x2022_06_26 real32,
      x2022_06_27 real32, x2022_06_28 real32, x2022_06_29 real32, x2022_06_30 real32, x2022_07_01 real32, x2022_07_02 real32, x2022_07_03 real32, x2022_07_04 real32, x2022_07_05 real32, x2022_07_06 real32, x2022_07_07 real32, x2022_07_08 real32, x2022_07_09 real32, x2022_07_10 real32, x2022_07_11 real32, x2022_07_12 real32, x2022_07_13 real32, x2022_07_14 real32, x2022_07_15 real32, x2022_07_16 real32, x2022_07_17 real32, x2022_07_18 real32, x2022_07_19 real32, x2022_07_20 real32, x2022_07_21 real32, x2022_07_22 real32, x2022_07_23 real32, x2022_07_24 real32, x2022_07_25 real32, x2022_07_26 real32,
      x2022_07_27 real32, x2022_07_28 real32, x2022_07_29 real32, x2022_07_30 real32, x2022_07_31 real32, x2022_08_01 real32, x2022_08_02 real32, x2022_08_03 real32, x2022_08_04 real32, x2022_08_05 real32, x2022_08_06 real32, x2022_08_07 real32, x2022_08_08 real32, x2022_08_09 real32, x2022_08_10 real32, x2022_08_11 real32, x2022_08_12 real32, x2022_08_13 real32, x2022_08_14 real32, x2022_08_15 real32, x2022_08_16 real32, x2022_08_17 real32, x2022_08_18 real32, x2022_08_19 real32, x2022_08_20 real32, x2022_08_21 real32, x2022_08_22 real32, x2022_08_23 real32, x2022_08_24 real32, x2022_08_25 real32,
      x2022_08_26 real32, x2022_08_27 real32, x2022_08_28 real32, x2022_08_29 real32, x2022_08_30 real32, x2022_08_31 real32, x2022_09_01 real32, x2022_09_02 real32, x2022_09_03 real32, x2022_09_04 real32, x2022_09_05 real32, x2022_09_06 real32, x2022_09_07 real32, x2022_09_08 real32, x2022_09_09 real32, x2022_09_10 real32, x2022_09_11 real32, x2022_09_12 real32, x2022_09_13 real32, x2022_09_14 real32, x2022_09_15 real32, x2022_09_16 real32, x2022_09_17 real32, x2022_09_18 real32, x2022_09_19 real32, x2022_09_20 real32, x2022_09_21 real32, x2022_09_22 real32, x2022_09_23 real32, x2022_09_24 real32,
      x2022_09_25 real32, x2022_09_26 real32, x2022_09_27 real32, x2022_09_28 real32, x2022_09_29 real32, x2022_09_30 real32, x2022_10_01 real32, x2022_10_02 real32, x2022_10_03 real32, x2022_10_04 real32, x2022_10_05 real32, x2022_10_06 real32, x2022_10_07 real32, x2022_10_08 real32, x2022_10_09 real32, x2022_10_10 real32, x2022_10_11 real32, x2022_10_12 real32, x2022_10_13 real32, x2022_10_14 real32, x2022_10_15 real32, x2022_10_16 real32, x2022_10_17 real32, x2022_10_18 real32, x2022_10_19 real32, x2022_10_20 real32, x2022_10_21 real32, x2022_10_22 real32, x2022_10_23 real32, x2022_10_24 real32,
      x2022_10_25 real32, x2022_10_26 real32, x2022_10_27 real32, x2022_10_28 real32, x2022_10_29 real32, x2022_10_30 real32, x2022_10_31 real32, x2022_11_01 real32, x2022_11_02 real32, x2022_11_03 real32, x2022_11_04 real32, x2022_11_05 real32, x2022_11_06 real32, x2022_11_07 real32, x2022_11_08 real32, x2022_11_09 real32, x2022_11_10 real32, x2022_11_11 real32, x2022_11_12 real32, x2022_11_13 real32, x2022_11_14 real32, x2022_11_15 real32, x2022_11_16 real32, x2022_11_17 real32, x2022_11_18 real32, x2022_11_19 real32, x2022_11_20 real32, x2022_11_21 real32, x2022_11_22 real32, x2022_11_23 real32,
      x2022_11_24 real32, x2022_11_25 real32, x2022_11_26 real32, x2022_11_27 real32, x2022_11_28 real32, x2022_11_29 real32, x2022_11_30 real32, x2022_12_01 real32, x2022_12_02 real32, x2022_12_03 real32, x2022_12_04 real32, x2022_12_05 real32, x2022_12_06 real32, x2022_12_07 real32, x2022_12_08 real32, x2022_12_09 real32, x2022_12_10 real32, x2022_12_11 real32, x2022_12_12 real32, x2022_12_13 real32, x2022_12_14 real32, x2022_12_15 real32, x2022_12_16 real32, x2022_12_17 real32, x2022_12_18 real32, x2022_12_19 real32, x2022_12_20 real32, x2022_12_21 real32, x2022_12_22 real32, x2022_12_23 real32,
      x2022_12_24 real32, x2022_12_25 real32, x2022_12_26 real32, x2022_12_27 real32, x2022_12_28 real32, x2022_12_29 real32, x2022_12_30 real32, x2022_12_31 real32, x2023_01_01 real32, x2023_01_02 real32, x2023_01_03 real32, x2023_01_04 real32, x2023_01_05 real32, x2023_01_06 real32, x2023_01_07 real32, x2023_01_08 real32, x2023_01_09 real32, x2023_01_10 real32, x2023_01_11 real32, x2023_01_12 real32, x2023_01_13 real32, x2023_01_14 real32, x2023_01_15 real32, x2023_01_16 real32, x2023_01_17 real32, x2023_01_18 real32, x2023_01_19 real32, x2023_01_20 real32, x2023_01_21 real32, x2023_01_22 real32,
      x2023_01_23 real32, x2023_01_24 real32, x2023_01_25 real32, x2023_01_26 real32, x2023_01_27 real32, x2023_01_28 real32, x2023_01_29 real32, x2023_01_30 real32, x2023_01_31 real32, x2023_02_01 real32, x2023_02_02 real32, x2023_02_03 real32, x2023_02_04 real32, x2023_02_05 real32, x2023_02_06 real32, x2023_02_07 real32, x2023_02_08 real32, x2023_02_09 real32, x2023_02_10 real32, x2023_02_11 real32, x2023_02_12 real32, x2023_02_13 real32, x2023_02_14 real32, x2023_02_15 real32, x2023_02_16 real32, x2023_02_17 real32, x2023_02_18 real32, x2023_02_19 real32, x2023_02_20 real32, x2023_02_21 real32,
      x2023_02_22 real32, x2023_02_23 real32, x2023_02_24 real32, x2023_02_25 real32, x2023_02_26 real32, x2023_02_27 real32, x2023_02_28 real32, x2023_03_01 real32, x2023_03_02 real32, x2023_03_03 real32, x2023_03_04 real32, x2023_03_05 real32, x2023_03_06 real32, x2023_03_07 real32, x2023_03_08 real32, x2023_03_09 real32, x2023_03_10 real32, x2023_03_11 real32, x2023_03_12 real32, x2023_03_13 real32, x2023_03_14 real32, x2023_03_15 real32, x2023_03_16 real32, x2023_03_17 real32, x2023_03_18 real32, x2023_03_19 real32, x2023_03_20 real32, x2023_03_21 real32, x2023_03_22 real32, x2023_03_23 real32,
      x2023_03_24 real32, x2023_03_25 real32, x2023_03_26 real32, x2023_03_27 real32, x2023_03_28 real32, x2023_03_29 real32, x2023_03_30 real32, x2023_03_31 real32, x2023_04_01 real32, x2023_04_02 real32, x2023_04_03 real32, x2023_04_04 real32, x2023_04_05 real32, x2023_04_06 real32, x2023_04_07 real32, x2023_04_08 real32, x2023_04_09 real32, x2023_04_10 real32, x2023_04_11 real32, x2023_04_12 real32, x2023_04_13 real32, x2023_04_14 real32, x2023_04_15 real32, x2023_04_16 real32, x2023_04_17 real32, x2023_04_18 real32, x2023_04_19 real32, x2023_04_20 real32, x2023_04_21 real32, x2023_04_22 real32,
      x2023_04_23 real32, x2023_04_24 real32, x2023_04_25 real32, x2023_04_26 real32, x2023_04_27 real32, x2023_04_28 real32, x2023_04_29 real32, x2023_04_30 real32, x2023_05_01 real32, x2023_05_02 real32, x2023_05_03 real32, x2023_05_04 real32, x2023_05_05 real32, x2023_05_06 real32, x2023_05_07 real32, x2023_05_08 real32, x2023_05_09 real32, x2023_05_10 real32, x2023_05_11 real32, x2023_05_12 real32, x2023_05_13 real32, x2023_05_14 real32, x2023_05_15 real32, x2023_05_16 real32, x2023_05_17 real32, x2023_05_18 real32, x2023_05_19 real32, x2023_05_20 real32, x2023_05_21 real32, x2023_05_22 real32,
      x2023_05_23 real32, x2023_05_24 real32, x2023_05_25 real32, x2023_05_26 real32, x2023_05_27 real32, x2023_05_28 real32, x2023_05_29 real32, x2023_05_30 real32, x2023_05_31 real32, x2023_06_01 real32, x2023_06_02 real32, x2023_06_03 real32, x2023_06_04 real32, x2023_06_05 real32, x2023_06_06 real32, x2023_06_07 real32, x2023_06_08 real32, x2023_06_09 real32, x2023_06_10 real32, x2023_06_11 real32, x2023_06_12 real32, x2023_06_13 real32, x2023_06_14 real32, x2023_06_15 real32, x2023_06_16 real32, x2023_06_17 real32, x2023_06_18 real32, x2023_06_19 real32, x2023_06_20 real32, x2023_06_21 real32,
      x2023_06_22 real32, x2023_06_23 real32, x2023_06_24 real32, x2023_06_25 real32, x2023_06_26 real32, x2023_06_27 real32, x2023_06_28 real32, x2023_06_29 real32, x2023_06_30 real32, x2023_07_01 real32, x2023_07_02 real32, x2023_07_03 real32, x2023_07_04 real32, x2023_07_05 real32, x2023_07_06 real32, x2023_07_07 real32, x2023_07_08 real32, x2023_07_09 real32, x2023_07_10 real32, x2023_07_11 real32, x2023_07_12 real32, x2023_07_13 real32, x2023_07_14 real32, x2023_07_15 real32, x2023_07_16 real32, x2023_07_17 real32, x2023_07_18 real32, x2023_07_19 real32, x2023_07_20 real32, x2023_07_21 real32,
      x2023_07_22 real32, x2023_07_23 real32, x2023_07_24 real32, x2023_07_25 real32, x2023_07_26 real32, x2023_07_27 real32, x2023_07_28 real32, x2023_07_29 real32, x2023_07_30 real32, x2023_07_31 real32, x2023_08_01 real32, x2023_08_02 real32, x2023_08_03 real32, x2023_08_04 real32, x2023_08_05 real32, x2023_08_06 real32, x2023_08_07 real32, x2023_08_08 real32, x2023_08_09 real32, x2023_08_10 real32, x2023_08_11 real32, x2023_08_12 real32, x2023_08_13 real32, x2023_08_14 real32, x2023_08_15 real32, x2023_08_16 real32, x2023_08_17 real32, x2023_08_18 real32, x2023_08_19 real32, x2023_08_20 real32,
      x2023_08_21 real32, x2023_08_22 real32, x2023_08_23 real32, x2023_08_24 real32, x2023_08_25 real32, x2023_08_26 real32, x2023_08_27 real32, x2023_08_28 real32, x2023_08_29 real32, x2023_08_30 real32, x2023_08_31 real32, x2023_09_01 real32, x2023_09_02 real32, x2023_09_03 real32, x2023_09_04 real32, x2023_09_05 real32, x2023_09_06 real32, x2023_09_07 real32, x2023_09_08 real32, x2023_09_09 real32, x2023_09_10 real32, x2023_09_11 real32, x2023_09_12 real32, x2023_09_13 real32, x2023_09_14 real32, x2023_09_15 real32, x2023_09_16 real32, x2023_09_17 real32, x2023_09_18 real32, x2023_09_19 real32,
      x2023_09_20 real32, x2023_09_21 real32, x2023_09_22 real32, x2023_09_23 real32, x2023_09_24 real32, x2023_09_25 real32, x2023_09_26 real32, x2023_09_27 real32, x2023_09_28 real32, x2023_09_29 real32, x2023_09_30 real32, x2023_10_01 real32, x2023_10_02 real32, x2023_10_03 real32, x2023_10_04 real32, x2023_10_05 real32, x2023_10_06 real32, x2023_10_07 real32, x2023_10_08 real32, x2023_10_09 real32, x2023_10_10 real32, x2023_10_11 real32, x2023_10_12 real32, x2023_10_13 real32, x2023_10_14 real32, x2023_10_15 real32, x2023_10_16 real32, x2023_10_17 real32, x2023_10_18 real32, x2023_10_19 real32,
      x2023_10_20 real32, x2023_10_21 real32, x2023_10_22 real32, x2023_10_23 real32, x2023_10_24 real32, x2023_10_25 real32, x2023_10_26 real32, x2023_10_27 real32, x2023_10_28 real32, x2023_10_29 real32, x2023_10_30 real32, x2023_10_31 real32, x2023_11_01 real32, x2023_11_02 real32, x2023_11_03 real32, x2023_11_04 real32, x2023_11_05 real32, x2023_11_06 real32, x2023_11_07 real32, x2023_11_08 real32, x2023_11_09 real32, x2023_11_10 real32, x2023_11_11 real32, x2023_11_12 real32, x2023_11_13 real32, x2023_11_14 real32, x2023_11_15 real32, x2023_11_16 real32, x2023_11_17 real32, x2023_11_18 real32,
      x2023_11_19 real32, x2023_11_20 real32, x2023_11_21 real32, x2023_11_22 real32, x2023_11_23 real32, x2023_11_24 real32, x2023_11_25 real32, x2023_11_26 real32, x2023_11_27 real32, x2023_11_28 real32, x2023_11_29 real32, x2023_11_30 real32
    -> AttributeKeeper_TR

Bookmark: nettoyage
Note: garder les colones utiles et où il ya de la donnée
AttributeKeeper_TR
    CREATE_BULK_MODE_FEATURES = NO
    KEEP_ATTRS = camera_road,traffic_camera,traffic_source,WKT,x2022_05_01,x2022_05_02,x2022_05_03,x2022_05_04,x2022_05_05,x2022_05_06,x2022_05_07,x2022_05_08,x2022_05_09,x2022_05_10,x2022_05_11,x2022_05_12,x2022_05_13,x2022_05_14,x2022_05_15,x2022_05_16,x2022_05_17,x2022_05_18,x2022_05_19,x2022_05_20,x2022_05_21,x2022_05_22,x2022_05_23,x2022_05_24,x2022_05_25,x2022_05_26,x2022_05_27,x2022_05_28,x2022_05_29,x2022_05_30,x2022_05_31,x2022_06_01,x2022_06_02,x2022_06_03,x2022_06_04,x2022_06_05,x2022_06_06,x2022_06_07,x2022_06_08,x2022_06_09,x2022_06_10,x2022_06_11,x2022_06_12,x2022_06_13,x2022_06_14,x2022_06_15,x2022_06_16,x2022_06_17,x2022_06_18,x2022_06_19,x2022_06_20,x2022_06_21,x2022_06_22,x2022_07_05,x2022_07_06,x2022_07_07,x2022_07_08,x2022_07_09,x2022_07_10,x2022_07_11,x2022_07_12,x2022_07_13,x2022_07_14,x2022_07_15,x2022_07_16,x2022_07_17,x2022_07_18,x2022_07_19,x2022_07_21,x2022_07_22,x2022_07_23,x2022_07_24,x2022_07_25,x2022_07_26,x2022_07_27,x2022_07_28,x2022_07_29,x2022_07_30,x2022_07_31,x2022_08_01,x2022_08_02,x2022_08_03,x2022_08_04,x2022_08_05,x2022_08_06,x2022_08_07,x2022_08_08,x2022_08_09,x2022_08_10,x2022_08_11,x2022_08_12,x2022_08_13,x2022_08_14,x2022_08_15,x2022_08_16,x2022_08_17,x2022_08_18,x2022_08_19,x2022_08_20,x2022_08_21,x2022_08_22,x2022_08_29,x2022_08_30,x2022_08_31,x2022_09_01,x2022_09_02,x2022_09_03,x2022_09_04,x2022_09_05,x2022_09_06,x2022_09_07,x2022_09_08,x2022_09_09,x2022_09_10,x2022_09_11,x2022_09_12,x2022_09_13,x2022_09_14,x2022_09_15,x2022_09_16,x2022_09_17,x2022_09_18,x2022_09_19,x2022_07_20,x2022_09_20,x2022_09_21,x2022_09_22,x2022_09_23,x2022_09_24,x2022_09_25,x2022_09_26,x2022_09_27,x2022_09_28,x2022_09_29,x2022_09_30,x2022_10_01,x2022_10_02,x2022_10_03,x2022_10_04,x2022_10_05,x2022_10_06,x2022_10_07,x2022_10_08,x2022_10_09,x2022_10_10,x2022_10_11,x2022_10_12,x2022_10_13,x2022_10_14,x2022_10_15,x2022_10_16,x2022_10_17,x2022_10_18,x2022_10_31,x2022_11_01,x2022_11_02,x2022_11_03,x2022_11_10,x2022_11_11,x2022_11_12,x2022_11_13,x2022_11_14,x2022_11_15,x2022_11_16,x2022_11_17,x2022_11_18,x2022_11_19,x2022_11_20,x2022_11_21,x2022_11_22,x2022_11_23,x2022_11_24,x2022_11_25,x2022_11_26,x2022_11_27,x2022_11_28,x2022_11_29,x2022_11_30,x2022_12_01,x2022_12_02,x2022_12_03,x2022_12_04,x2022_12_05,x2022_12_06,x2022_12_07,x2022_12_08,x2022_12_09,x2022_12_10,x2022_12_11,x2022_12_12,x2022_12_13,x2022_12_14,x2022_12_15,x2022_12_16,x2022_12_17,x2022_12_18,x2022_12_19,x2022_12_20,x2022_12_21,x2022_12_22,x2022_12_23,x2022_12_24,x2022_12_25,x2022_12_26,x2022_12_27,x2023_01_06,x2023_01_07,x2023_01_08,x2023_01_09,x2023_01_10,x2023_01_11,x2023_01_12,x2023_01_13,x2023_01_14,x2023_01_15,x2023_01_16,x2023_01_17,x2023_01_18,x2023_01_19,x2023_01_20,x2023_01_21,x2023_01_22,x2023_01_23,x2023_01_24,x2023_01_25,x2023_01_26,x2023_01_27,x2023_01_28,x2023_01_29,x2023_01_30,x2023_01_31,x2023_02_01,x2023_02_02,x2023_02_03,x2023_02_04,x2023_02_05,x2023_02_06,x2023_02_07,x2023_02_08,x2023_02_09,x2023_02_10,x2023_02_11,x2023_02_12,x2023_02_19,x2023_02_20,x2023_02_21,x2023_02_22,x2023_02_23,x2023_02_24,x2023_02_25,x2023_02_26,x2023_02_27,x2023_02_28,x2023_03_01,x2023_03_02,x2023_03_03,x2023_03_04,x2023_03_05,x2023_03_06,x2023_03_07,x2023_03_08,x2023_03_09,x2023_03_10,x2023_03_11,x2023_03_12,x2023_03_13,x2023_03_14,x2023_03_15,x2023_03_16,x2023_03_17,x2023_03_18,x2023_03_19,x2023_03_20,x2023_03_21,x2023_03_22,x2023_03_23,x2023_03_24,x2023_03_25,x2023_03_26,x2023_03_27,x2023_03_28,x2023_03_29,x2023_03_30,x2023_03_31,x2023_04_01,x2023_04_02,x2023_04_14,x2023_04_15,x2023_04_16,x2023_04_17,x2023_04_18,x2023_04_19,x2023_04_20,x2023_04_21,x2023_04_22,x2023_04_23,x2023_04_24,x2023_04_25,x2023_04_26,x2023_04_27,x2023_04_28,x2023_04_29,x2023_04_30,x2023_05_01,x2023_05_02,x2023_05_03,x2023_05_04,x2023_05_05,x2023_05_06,x2023_05_07,x2023_05_08,x2023_05_09,x2023_05_10,x2023_05_11,x2023_05_12,x2023_05_13,x2023_05_14,x2023_05_15,x2023_05_16,x2023_05_17,x2023_05_18,x2023_05_19,x2023_05_20,x2023_05_21,x2023_05_22,x2023_05_23,x2023_05_24,x2023_05_25,x2023_05_26,x2023_05_27,x2023_05_28,x2023_05_29,x2023_05_30,x2023_05_31,x2023_06_01,x2023_06_02,x2023_06_03,x2023_06_04,x2023_06_05,x2023_06_06,x2023_06_07,x2023_06_08,x2023_06_09,x2023_06_10,x2023_06_11,x2023_06_12,x2023_06_13,x2023_06_14,x2023_06_15,x2023_06_16,x2023_06_17,x2023_06_18,x2023_06_19,x2023_06_20,x2023_06_21,x2023_06_22,x2023_06_23,x2023_06_24,x2023_06_25,x2023_06_26,x2023_06_27,x2023_06_28,x2023_06_29,x2023_06_30,x2023_07_01,x2023_07_02,x2023_07_03,x2023_07_04,x2023_07_05,x2023_07_06,x2023_07_07,x2023_07_08,x2023_07_09,x2023_07_10,x2023_07_11,x2023_07_12,x2023_07_13,x2023_07_14,x2023_07_15,x2023_07_16,x2023_07_17,x2023_07_18,x2023_07_19,x2023_07_20,x2023_07_21,x2023_07_22,x2023_07_23,x2023_07_24,x2023_07_25,x2023_07_26,x2023_07_27,x2023_07_28,x2023_07_29,x2023_07_30,x2023_07_31,x2023_08_01,x2023_08_02,x2023_08_03,x2023_08_04,x2023_08_05,x2023_08_06,x2023_08_07,x2023_08_08,x2023_08_09,x2023_08_10,x2023_08_11,x2023_08_12,x2023_08_13,x2023_08_14,x2023_08_15,x2023_08_16,x2023_08_17,x2023_08_18,x2023_08_19,x2023_08_20,x2023_08_21,x2023_08_22,x2023_08_23,x2023_08_24,x2023_08_25,x2023_08_26,x2023_08_27,x2023_08_28,x2023_08_29,x2023_08_30,x2023_08_31,x2023_09_01,x2023_09_02,x2023_09_03,x2023_09_04,x2023_09_05,x2023_09_06,x2023_09_07,x2023_09_08,x2023_09_09,x2023_09_10,x2023_09_11,x2023_09_12,x2023_09_13,x2023_09_14,x2023_09_15,x2023_09_16,x2023_09_17,x2023_09_18,x2023_09_19,x2023_09_20,x2023_09_21,x2023_09_22,x2023_09_23,x2023_09_24,x2023_09_25,x2023_09_26,x2023_09_27,x2023_09_28,x2023_09_29,x2023_09_30,x2023_10_10,x2023_10_11,x2023_10_12,x2023_10_13,x2023_10_14,x2023_10_15,x2023_10_16,x2023_10_17,x2023_10_18,x2023_10_19,x2023_10_20,x2023_10_21,x2023_10_22,x2023_10_23,x2023_10_24,x2023_10_25,x2023_10_26,x2023_10_27,x2023_10_28,x2023_10_29,x2023_10_30,x2023_10_31,x2023_11_01,x2023_11_02,x2023_11_03,x2023_11_04,x2023_11_05,x2023_11_06,x2023_11_07,x2023_11_08,x2023_11_09,x2023_11_10,x2023_11_11,x2023_11_12,x2023_11_13,x2023_11_14,x2023_11_15,x2023_11_16,x2023_11_17,x2023_11_18,x2023_11_19,x2023_11_20,x2023_11_21,x2023_11_22,x2023_11_23,x2023_11_24,x2023_11_25,x2023_11_26,x2023_11_27,x2023_11_28,x2023_11_29,x2023_11_30
    -> Tester_3
Note: garder la ville de montréal
Tester_3
    BOOL_OP = COMPOSITE
    COMPOSITE_TEST = 1 AND 2 AND 3 AND 4
    TEST_CLAUSE:
      CASE_SENSITIVE_TEST @Value(traffic_source) NOT_= Alberta
      CASE_SENSITIVE_TEST @Value(traffic_source) NOT_LIKE Calgary
      CASE_SENSITIVE_TEST @Value(traffic_source) NOT_LIKE Ontario
      CASE_SENSITIVE_TEST @Value(traffic_source) NOT_LIKE Toronto
    TEST_MODE = CASE_SENSITIVE_TEST
    PASSED -> AttributeRenamer
    FAILED -> Logger_3
Note: renomer les colones
AttributeRenamer
    ATTR_TABLE:
      RENAME_SET_DEFAULT WKT > position
      RENAME_SET_DEFAULT camera_road > intersection_de_rue
      RENAME_SET_DEFAULT traffic_camera > numero_camera
      RENAME_SET_DEFAULT traffic_source > ville
    MISSING_INPUT_ATTRS = REMOVE
    -> AttributeCreator
Note: autres villes
Logger_3
    LOG_FEATURE = LOG_ONLY
    MAXCOORDS = 20
    MAXFEATS = 20
    MESSAGE = Feature is:
    SEVERITY = INFO

Bookmark: traitement statistique
Note: ajout des attributs longitude et lattitude
AttributeCreator
    ATTR_TABLE:
      SET_TO longitude = @Evaluate(mid(<@Value(position)>, 8, 12))
      SET_TO latitude = @Value(position)
    -> StatisticsCalculator
Note: calcul nombre de voiture médian à chaque jour
StatisticsCalculator
    CALCULATION_MODE = NUMERIC
    FEAT_STATS =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
    COMPLETE -> Reprojector_4

Bookmark: reprojection
Reprojector_4
    DEST = EPSG:3857
    INTERPOLATION_TYPE_NAME = Nearest Neighbor
    RASTER_CELL_SIZE = Preserve Cells
    RASTER_TOLERANCE = 0.0
    REPROJECTED -> StringReplacer

Bookmark: traitement de l'attribut POOSITION
StringReplacer
    CASE = NO
    FIND_TEXT = POINT
    NO_MATCH = _FME_NO_OP_
    REGEXP = NO
    SRC_ATTRS = position
    -> StringReplacer_2
StringReplacer_2
    CASE = NO
    FIND_TEXT = (
    NO_MATCH = _FME_NO_OP_
    REGEXP = NO
    SRC_ATTRS = position
    -> StringReplacer_3
StringReplacer_3
    CASE = NO
    FIND_TEXT = )
    NO_MATCH = _FME_NO_OP_
    REGEXP = NO
    SRC_ATTRS = position

Bookmark: données parc issu du labo 3
espvert.esv_espace_vert_vue_datefin_null (reader GEOJSON_1)
    attributes: OBJECTID string, Type string, Lien string, Nom string, NUM_INDEX string, SUPERFICIE string, PROPRIETE string, GESTION string, COMPETENCE string, TYPO1 string, TYPO2 string
    -> AttributeKeeper

Bookmark: nettoyage
Note: colones utiles
AttributeKeeper
    CREATE_BULK_MODE_FEATURES = NO
    KEEP_ATTRS = Nom,OBJECTID,TYPO1,TYPO2,SUPERFICIE,COMPETENCE
    -> Tester
Note: filtrer les lignes
Tester
    BOOL_OP = COMPOSITE
    COMPOSITE_TEST = 1 AND 2 AND 3 AND 4 AND 5 AND 6 AND 7 AND 8 AND 9 AND 10
    TEST_CLAUSE:
      CASE_INSENSITIVE_TEST @Value(COMPETENCE) NOT_CONTAINS Privé
      CASE_INSENSITIVE_TEST @Value(TYPO1) NOT_CONTAINS En cours de validation
      CASE_INSENSITIVE_TEST @Value(TYPO2) NOT_CONTAINS Rue piétonne
      CASE_INSENSITIVE_TEST @Value(TYPO2) NOT_CONTAINS Bande gazonnée
      CASE_INSENSITIVE_TEST @Value(TYPO2) NOT_CONTAINS Toit-vert
      CASE_INSENSITIVE_TEST @Value(TYPO2) NOT_CONTAINS Ruelle verte
      CASE_INSENSITIVE_TEST @Value(TYPO2) NOT_CONTAINS Passage
      CASE_INSENSITIVE_TEST @Value(TYPO2) NOT_CONTAINS Parc école
      CASE_INSENSITIVE_TEST @Value(TYPO2) NOT_CONTAINS Rue piétonne
      CASE_INSENSITIVE_TEST @Value(TYPO2) NOT_CONTAINS Rue partagée
    TEST_MODE = CASE_INSENSITIVE_TEST
    PASSED -> Reprojector_5
    FAILED -> Logger
Logger
    LOG_FEATURE = LOG_ONLY
    MAXCOORDS = 20
    MAXFEATS = 20
    MESSAGE = Feature is:
    SEVERITY = INFO

Bookmark: vers base de dnnées
espace_parc_mtl (writer POSTGIS_4)
    attributes: objectid text, nom text, superficie text, competence text, typo1 text, typo2 text

Bookmark: données secteur montreal
rsqa_secteurs_4326 (reader GEOJSON_2)
    attributes: id int, lettre string, nom string
    -> Reprojector

Bookmark: IQA tps reel
CSV (reader CSV2_2)
    attributes: stationId uint32, polluant varchar(4), valeur uint32, date date, heure uint32
    -> StringReplacer_15

Bookmark: nettoyage
Note: numératation des stations
StringReplacer_15
    CASE = NO
    FIND_TEXT = 3
    NO_MATCH = _FME_NO_OP_
    REGEXP = NO
    REPLACE_TEXT = 1
    SRC_ATTRS = stationId
    -> StringReplacer_16
StringReplacer_16
    CASE = NO
    FIND_TEXT = 6
    NO_MATCH = _FME_NO_OP_
    REGEXP = NO
    REPLACE_TEXT = 2
    SRC_ATTRS = stationId
    -> StringReplacer_17
StringReplacer_17
    CASE = NO
    FIND_TEXT = 17
    NO_MATCH = _FME_NO_OP_
    REGEXP = NO
    REPLACE_TEXT = 3
    SRC_ATTRS = stationId
    -> StringReplacer_18
StringReplacer_18
    CASE = NO
    FIND_TEXT = 28
    NO_MATCH = _FME_NO_OP_
    REGEXP = NO
    REPLACE_TEXT = 4
    SRC_ATTRS = stationId
    -> StringReplacer_19
StringReplacer_19
    CASE = NO
    FIND_TEXT = 101
    NO_MATCH = _FME_NO_OP_
    REGEXP = NO
    REPLACE_TEXT = 5
    SRC_ATTRS = stationId
    -> StringReplacer_20
StringReplacer_20
    CASE = NO
    FIND_TEXT = 50
    NO_MATCH = _FME_NO_OP_
    REGEXP = NO
    REPLACE_TEXT = 6
    SRC_ATTRS = stationId
    -> StringReplacer_21
StringReplacer_21
    CASE = NO
    FIND_TEXT = 55
    NO_MATCH = _FME_NO_OP_
    REGEXP = NO
    REPLACE_TEXT = 7
    SRC_ATTRS = stationId
    -> StringReplacer_22
StringReplacer_22
    CASE = NO
    FIND_TEXT = 22
    NO_MATCH = _FME_NO_OP_
    REGEXP = NO
    REPLACE_TEXT = 8
    SRC_ATTRS = stationId
    -> StringReplacer_23
StringReplacer_23
    CASE = NO
    FIND_TEXT = 80
    NO_MATCH = _FME_NO_OP_
    REGEXP = NO
    REPLACE_TEXT = 9
    SRC_ATTRS = stationId
    -> StringReplacer_24
StringReplacer_24
    CASE = NO
    FIND_TEXT = 99
    NO_MATCH = _FME_NO_OP_
    REGEXP = NO
    REPLACE_TEXT = 10
    SRC_ATTRS = stationId
    -> StringReplacer_25
StringReplacer_25
    CASE = NO
    FIND_TEXT = 103
    NO_MATCH = _FME_NO_OP_
    REGEXP = NO
    REPLACE_TEXT = 11
    SRC_ATTRS = stationId
    -> Reprojector_2

Bookmark: IQA /station
CSV (reader CSV2_3)
    attributes: stationId uint32, adresse varchar(50), latitude y_coordinate, longitude x_coordinate, X real64, Y real64, polluant varchar(4), valeur uint32, date date, heure uint32
    -> StringReplacer_4

Bookmark: nettoyage
Note: renommmer
StringReplacer_4
    CASE = NO
    FIND_TEXT = 7650 rue ChÃ¢teauneuf
    NO_MATCH = _FME_NO_OP_
    REGEXP = NO
    REPLACE_TEXT = 7650 rue Chateauneuf
    SRC_ATTRS = adresse
    -> StringReplacer_5
Note: renommer
Note: reporjection
StringReplacer_5
    CASE = NO
    FIND_TEXT = AÃ©roport de MontrÃ©al, 90-A rue HervÃ©-St-Martin
    NO_MATCH = _FME_NO_OP_
    REGEXP = NO
    REPLACE_TEXT = Aéroport de Montréal, 90-A rue Hervé-St-Martin
    SRC_ATTRS = adresse
    -> StringReplacer_6
Note: renommer
StringReplacer_6
    CASE = NO
    FIND_TEXT = 12400, Wilfrid-Ouellette, coin Louis-LumiÃ¨re
    NO_MATCH = _FME_NO_OP_
    REGEXP = NO
    REPLACE_TEXT = 12400, Wilfrid-Ouellette, coin Louis-Lumiere
    SRC_ATTRS = adresse
    -> Reprojector_8

Bookmark: traitement
AttributeManager_2
    ATTR_TABLE = RENAME_SET_VALUE polluant > polluant_majeur
    -> Renomer_la_colonne_stationld
Renomer_la_colonne_stationld: AttributeRenamer
    ATTR_TABLE:
      RENAME_SET_DEFAULT stationId > Station
      RENAME_SET_DEFAULT adresse > Adresse
      RENAME_SET_DEFAULT date > Date
      RENAME_SET_DEFAULT heure > Heure
      RENAME_SET_DEFAULT latitude > Latitude
      RENAME_SET_DEFAULT polluant > Polluant
      RENAME_SET_DEFAULT longitude > Longitude
      RENAME_SET_DEFAULT valeur > Valeur
    MISSING_INPUT_ATTRS = REMOVE
    -> FeatureMerger [REQUESTOR]
    -> iqa_par_station (writer POSTGIS_4)

Bookmark: ajout à la base de donnée
Note: connection a la base de donnees
iqa_par_station (writer POSTGIS_4)
    attributes: stationid int8, adresse varchar(50), latitude float8, longitude float8, x float8, y float8, polluant varchar(4), valeur int8, date date, heure int8

Bookmark: liste des stations
CSV (reader CSV2_1)
    attributes: numero_station uint32, SNPA uint32, statut varchar(7), nom varchar(24), adresse varchar(54), arrondissement_ville varchar(26), latitude y_coordinate, longitude x_coordinate, X real64, Y real64, secteur_id uint32, secteur_nom varchar(13), hauteur uint32
    -> AttributeKeeper_3

Bookmark: nettoyage et traitement
AttributeKeeper_3
    CREATE_BULK_MODE_FEATURES = NO
    KEEP_ATTRS = adresse,numero_station,statut
    -> StringReplacer_7
StringReplacer_7
    CASE = NO
    FIND_TEXT = fermÃ©
    NO_MATCH = _FME_NO_OP_
    REGEXP = NO
    REPLACE_TEXT = Fermé
    SRC_ATTRS = statut
    -> StringReplacer_8
StringReplacer_8
    CASE = NO
    FIND_TEXT = Jardin Botanique, MontrÃ©al
    NO_MATCH = _FME_NO_OP_
    REGEXP = NO
    REPLACE_TEXT = Jardin Botanique, Montréal
    SRC_ATTRS = adresse
    -> StringReplacer_9
StringReplacer_9
    CASE = NO
    FIND_TEXT = 7650 rue ChÃ¢teauneuf
    NO_MATCH = _FME_NO_OP_
    REGEXP = NO
    REPLACE_TEXT = 7650 rue Chateauneuf
    SRC_ATTRS = adresse
    -> StringReplacer_10
StringReplacer_10
    CASE = NO
    FIND_TEXT = ArÃ©na ChÃ©nier (coin ChÃ©nier et Avenue de l'ArÃ©na)
    NO_MATCH = _FME_NO_OP_
    REGEXP = NO
    REPLACE_TEXT = Aréna Chénier (coin Chénier et Avenue de l'Aréna)
    SRC_ATTRS = adresse
    -> StringReplacer_11
StringReplacer_11
    CASE = NO
    FIND_TEXT = 12145 boul. RiviÃ¨re-des-Prairies
    NO_MATCH = _FME_NO_OP_
    REGEXP = NO
    REPLACE_TEXT = 12145 boul. Riviere-des-Prairies
    SRC_ATTRS = adresse
    -> StringReplacer_12
StringReplacer_12
    CASE = NO
    FIND_TEXT = 12400, Wilfrid-Ouellette, coin Louis-LumiÃ¨re
    NO_MATCH = _FME_NO_OP_
    REGEXP = NO
    REPLACE_TEXT = 12400, Wilfrid-Ouellette, coin Louis-Lumiere
    SRC_ATTRS = adresse
    -> StringReplacer_13
StringReplacer_13
    CASE = NO
    FIND_TEXT = ouvert
    NO_MATCH = _FME_NO_OP_
    REGEXP = NO
    REPLACE_TEXT = Ouvert
    SRC_ATTRS = statut
    -> StringReplacer_14
StringReplacer_14
    CASE = NO
    FIND_TEXT = AÃ©roport de MontrÃ©al, 90-A rue HervÃ©-St-Martin
    NO_MATCH = _FME_NO_OP_
    REGEXP = NO
    REPLACE_TEXT = Aéroport de Montréal, 90-A rue Hervé-St-Martin
    SRC_ATTRS = adresse
    -> AttributeRenamer_2
AttributeRenamer_2
    ATTR_TABLE:
      RENAME_SET_DEFAULT numero_station > Numéro de la station
      RENAME_SET_DEFAULT adresse > Adresse
      RENAME_SET_DEFAULT statut > Statut
    MISSING_INPUT_ATTRS = REMOVE
    -> AttributeFilter
Note: Filter les stations ouvertes / fermées
AttributeFilter
    ATTR_NAME = Statut
    ATTR_VALUES = <Empty>,<Missing>,<Null>,<Unfiltered>,Ouvert
    <UNFILTERED> -> Logger_6
    Ouvert -> Counter
Counter
    CNT_ATTR = _count
    DOMAIN = counter
    SCOPE = Global
    START = 1
    -> AttributeRenamer_3
AttributeRenamer_3
    ATTR_TABLE = RENAME_SET_DEFAULT _count > Numéro des stations
    MISSING_INPUT_ATTRS = REMOVE
    -> AttributeKeeper_4
AttributeKeeper_4
    CREATE_BULK_MODE_FEATURES = NO
    KEEP_ATTRS = Adresse,Numéro des stations,Statut
    -> FeatureMerger_2 [SUPPLIER]
    -> FeatureMerger [SUPPLIER]
Logger_6
    LOG_FEATURE = LOG_ONLY
    MAXCOORDS = 20
    MAXFEATS = 20
    MESSAGE = Feature is:
    SEVERITY = INFO

Bookmark: Fusion des tableaux
FeatureMerger
    ATTR_ACCUM_MODE = Merge Supplier
    ATTR_CONFLICT_RES = Use Requestor
    IGNORE_NULLS = No
    JOIN_KEYS = @Value(Station) @Value(Numéro des stations) AUTO @Value(Adresse) @Value(Adresse) AUTO @Value(Date)  AUTO @Value(Heure)  AUTO @Value(Latitude)  AUTO @Value(Longitude)  AUTO @Value(Polluant)  AUTO @Value(X)  AUTO @Value(Y)  AUTO
    MERGE_TYPE = Attributes Only
    PROCESS_DUPS = NO
    REJECT_NULL_MISSING_KEYS = No
    SUPPLIERS_FIRST = Yes
    UNMERGED_REQUESTOR -> AttributeManager
    <REJECTED> -> Logger_7
Logger_7
    LOG_FEATURE = LOG_ONLY
    MAXCOORDS = 20
    MAXFEATS = 20
    MESSAGE = Feature is:
    SEVERITY = INFO

Bookmark: Renommer les lignes (stations)
Station_1: StringReplacer
    CASE = NO
    FIND_TEXT = 3
    NO_MATCH = _FME_NO_OP_
    REGEXP = NO
    REPLACE_TEXT = 1
    SRC_ATTRS = Station
    -> Station_2
Station_2: StringReplacer
    CASE = NO
    FIND_TEXT = 6
    NO_MATCH = _FME_NO_OP_
    REGEXP = NO
    REPLACE_TEXT = 2
    SRC_ATTRS = Station
    -> Station_3
Station_3: StringReplacer
    CASE = NO
    FIND_TEXT = 17
    NO_MATCH = _FME_NO_OP_
    REGEXP = NO
    REPLACE_TEXT = 3
    SRC_ATTRS = Station
    -> Station_4
Station_4: StringReplacer
    CASE = NO
    FIND_TEXT = 28
    NO_MATCH = _FME_NO_OP_
    REGEXP = NO
    REPLACE_TEXT = 4
    SRC_ATTRS = Station
    -> Station_5
Station_5: StringReplacer
    CASE = NO
    FIND_TEXT = 11
    NO_MATCH = _FME_NO_OP_
    REGEXP = NO
    REPLACE_TEXT = 5
    SRC_ATTRS = Station
    -> Station_6
Station_6: StringReplacer
    CASE = NO
    FIND_TEXT = 50
    NO_MATCH = _FME_NO_OP_
    REGEXP = NO
    REPLACE_TEXT = 6
    SRC_ATTRS = Station
    -> Station_7
Station_7: StringReplacer
    CASE = NO
    FIND_TEXT = 55
    NO_MATCH = _FME_NO_OP_
    REGEXP = NO
    REPLACE_TEXT = 7
    SRC_ATTRS = Station
    -> Station_8
Station_8: StringReplacer
    CASE = NO
    FIND_TEXT = 22
    NO_MATCH = _FME_NO_OP_
    REGEXP = NO
    REPLACE_TEXT = 8
    SRC_ATTRS = Station
    -> Station_9
Station_9: StringReplacer
    CASE = NO
    FIND_TEXT = 80
    NO_MATCH = _FME_NO_OP_
    REGEXP = NO
    REPLACE_TEXT = 9
    SRC_ATTRS = Station
    -> Station_10
Station_10: StringReplacer
    CASE = NO
    FIND_TEXT = 99
    NO_MATCH = _FME_NO_OP_
    REGEXP = NO
    REPLACE_TEXT = 10
    SRC_ATTRS = Station
    -> Station_11
Station_11: StringReplacer
    CASE = NO
    FIND_TEXT = 101
    NO_MATCH = _FME_NO_OP_
    REGEXP = NO
    REPLACE_TEXT = 11
    SRC_ATTRS = Station
    -> FeatureMerger_2 [REQUESTOR]

Bookmark: Fusion
FeatureMerger_2
    ATTR_ACCUM_MODE = Merge Supplier
    ATTR_CONFLICT_RES = Use Requestor
    IGNORE_NULLS = No
    JOIN_KEYS = @Value(Adresse) @Value(Adresse) AUTO @Value(Station) @Value(Numéro des stations) AUTO
    MERGE_TYPE = Attributes Only
    PROCESS_DUPS = NO
    REJECT_NULL_MISSING_KEYS = No
    SUPPLIERS_FIRST = No
    MERGED -> Reprojector_11
    <REJECTED> -> Logger_10

Bookmark: jointure spatiale
Note: joindre les caméras avec les arrondissements
PointOnAreaOverlayer
    ATTR_ACCUM_MODE = Merge Incoming
    ATTR_CONFLICT_RES = Use Original
    DEAGGREGATE_INPUT = Yes
    OV_ATTR = point-count
    POLYS_FIRST = NO
    <REJECTED> -> Logger_2
Logger_2
    LOG_FEATURE = LOG_ONLY
    MAXCOORDS = 20
    MAXFEATS = 20
    MESSAGE = Feature is:
    SEVERITY = INFO
